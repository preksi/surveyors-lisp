;**********************************************
;***************  makro lisp  *****************
;**********************************************

;zajednièka datoteka svih makroa, koja se
;uèitava kod pokretanja AutoCAD-a pa su tipkovnièke
;kratice dostupne odmah, a mogu se koristiti i za VBA

;------------------- VBA makroi ---------------

(defun C:ay()
  (vl-vbarun"autopoli")
)
(defun C:kv()
  (vl-vbarun"konvert")
)
(defun C:sp()
  (vl-vbarun"spoj")
)
(defun C:z3()
  (vl-vbarun"zgrada3D")
)
(defun C:ff()
  (vl-vbarun"front")
)
(defun C:nm()
  (vl-vbarun"Nomenklatura")
)
(defun c:zz()
  (vl-vbarun"zekavac")
)
(defun c:rt()
  (vl-vbarun"rotacija")
)
(defun C:kk()
  (vl-vbarun"kartiranje")
)
(defun c:du()
  (vl-vbarun"dubina")
)
(defun c:rc()
  (vl-vbarun"rec")
)
(defun c:ii()
  (vl-vbarun"iskolcenje")
)
(defun c:ip()
  (vl-vbarun"InterPoli3D")
)
(defun c:pk()
  (vl-vbarun"pokos")
)
(defun c:gps()
  (vl-vbarun"GPSpolozajci")
)
(defun c:sa()
  (vl-vbarun"suma")
)
(defun c:lp()
  (vl-vbarun"layerPlus")
)
(defun c:rv()
  (vl-vbarun"razlika")
)
(defun c:vi()
  (vl-vbarun"visineISK")
)
(defun c:oo()
  (vl-vbarun"o2c")
)
(defun c:ko()
  (vl-vbarun"koordinate")
)
(defun c:ss()
  (vl-vbarun"setOpisa")
)
(defun c:rk()
  (vl-vbarun"rk")
)
(defun c:as()
  (vl-vbarun"aritmetickaSredina")
)
(defun c:pm()
  (vl-vbarun"pomoc")
)
(defun c:info()
  (vl-vbarun"info")
)
(defun c:mj()
  (vl-vbarun"promjenaMjerila")
)
(defun c:dof()
  (vl-vbarun"GPinsert") ;ostavljeno radi kompatibilnosti
)
(defun c:gp()
  (vl-vbarun"GPinsert")
)
(defun c:kr()
  (vl-vbarun"koordinateKriza")
)
(defun c:4k()
  (vl-vbarun"cetiriKriza")
)
(defun c:dm()
  (vl-vbarun"decmre")
)
(defun c:ooo()
  (vl-vbarun"offset3D")
)
(defun c:ka()
  (vl-vbarun"kartiranjeAtt")
)
(defun c:a2c()
  (vl-vbarun"att2csv")
)
(defun c:va()
  (vl-vbarun"visineAtt")
)

;------------------- LISP makroi --------------


(defun c:ee ()
   ;makro lisp koji otvara Windows Explorer u direktoriju
   ;u kojem se nalazi trenutno aktivni DWG
  (startapp "explorer" (strcat "/n,/e," (getvar "dwgprefix")))
  (princ)
)

(defun c:pd()
  ;popravljanje dijaloga promjenom varijable FILEDIA
  (setvar "FILEDIA" 1)
  (princ)
)

(defun c:if0()
  (setvar "cmdecho" 0)
  (command "_imageframe" "OFF")
  (command "_regen")
  (setvar "cmdecho" 1)
)

(defun c:if1()
  (setvar "cmdecho" 0)
  (command "_imageframe" "ON")
  (command "_regen")
  (setvar "cmdecho" 1)
)

(defun c:hb()
  ;hatch to back
  (command "_draworder" (ssget "_X" '((0 . "HATCH"))) "" "b" )
  (prompt "\nHatch2back ... gotovo!")(princ)
)

(defun c:fn()
  (command "_find")
)

(defun c:p0()
  (command "3dpoly")
)
(defun c:bb()
  (ai_draworder "_b")
)
(defun c:bf()
  (ai_draworder "_f")
)

(defun c:uo()
  (command "ucs" "ob" pause )
  (command "plan" "")
)

(defun c:ww()
  (COMMAND "ucs" "w" "")
  (command "plan" "")
  (princ)
)
